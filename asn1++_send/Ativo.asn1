Ativo DEFINITIONS AUTOMATIC TAGS ::=
BEGIN

Iniciate ::= SEQUENCE{
    name PrintableString(SIZE(1..20)),
    atop PrintableString(SIZE(1..20)),
    deviceType BOOLEAN
}

Data ::= SEQUENCE{
    payload PrintableString(SIZE(1..20))
}

Ativo ::= SEQUENCE{
    id CHOICE{
        iniciate Iniciate,
        data Data    
    }
}
 
END
